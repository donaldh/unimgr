module eventsource-uagent {
    yang-version 1;
    namespace "urn:opendaylight:params:xml:ns:yang:eventsource:uagent";
    prefix "eventsource-uagent";

    import config { prefix config; revision-date 2013-04-05; }
    import opendaylight-md-sal-binding { prefix md-sal-binding; revision-date 2013-10-28;}
    import opendaylight-md-sal-dom {prefix dom;}

    description
        "Service definition for eventsource-uagent project";

    revision "2015-04-08" {
        description
            "Initial revision";
    }

    identity eventsource-uagent {
        base config:module-type;
        config:java-name-prefix eventsourceUagent;
    }

    augment "/config:modules/config:module/config:configuration" {
        case eventsource-uagent {
            when "/config:modules/config:module/config:type = 'eventsource-uagent'";
            container broker {
                uses config:service-ref {
                    refine type {
                        mandatory true;
                        config:required-identity md-sal-binding:binding-broker-osgi-registry;
                    }
                }
            }

            container dom-broker {
                uses config:service-ref {
                    refine type {
                        mandatory true;
                        config:required-identity dom:dom-broker-osgi-registry;
                    }
                }
            }

            leaf output-file-name {
                type string {
                    length "1 .. 1024";
                    }
                description "Name of file where eventsource-uagent will write notification";
            } 

        }

    }
}
